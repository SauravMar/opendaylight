module hello {
    yang-version 1;
    namespace "urn:Opendaylight:params:xml:ns:yang:hello";
    prefix "hello";

    revision "2019-11-19" { // TODO change revision to date of model creation
        description "Initial revision of hello model";
    }

    rpc hello-world {
        input {
            leaf name {
                type string;
            }
        }
        output {
            leaf greeting {
                type string;
            }
        }
    }
}
